module cpqd-x {
    yang-version 1;
    namespace "http://cpqd.com.br/yang";

    description teste;
    prefix x;

    import cpqd-y {
        prefix y;
    }
    import cpqd-z {
        prefix "z";
        revision-date 2014-02-04;
    }

    include submodule;
    include submodule2
    {
        revision-date 2014-02-04;
    }

    revision 2014-02-04 {
        description "Versão mais nova";
    }
    revision 2014-01-30;

    typedef valores {
        type enumeration {
            enum um {
                value 1;
            }
            enum "dois ou três";
        }
    }

    typedef tipo {
        type texto {
            type string;
            pattern ".*" {
                error-message "that's impossible!";
            }
        }
        default "";
        units "chars";

        ns:extension argument {
            ns:extension2 argument2;
        }
    }

    /* Comment */
    container x {
        description "TODO abc"; // Line comment FIXME 
        leaf config {
            type enumeration {
                enum x;
            }
            tailf:info x;
        }
    }

    list y {
        key a;
        leaf a {
            type string;
            default "the default value";
        }
        leaf b {
            type leafref {
                path "/path/to/string/leaf";
            }
        }
    }
}
